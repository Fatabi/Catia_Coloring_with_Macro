Attribute VB_Name = "Module1"
Sub CATMain()

Dim partDocument1 As PartDocument
Set partDocument1 = CATIA.ActiveDocument

Dim part1 As Part
Set part1 = partDocument1.Part

Dim bodies1 As Bodies
Set bodies1 = part1.Bodies

Dim body1 As Body
Set body1 = bodies1.Item("PartBody")

Dim shapes1 As Shapes
Set shapes1 = body1.Shapes

Dim hole1 As Hole
Set hole1 = shapes1.Item("Hole.1")

hole1.ThreadingMode = catSmoothHoleThreading

hole1.ThreadSide = catRightThreadSide

part1.Update

End Sub

Attribute VB_Name = "Module2"
Sub CATMain()

End Sub

Attribute VB_Name = "Module3"
Sub CATMain()

Dim partDocument1 As PartDocument
Set partDocument1 = CATIA.ActiveDocument

Dim selection1 As Selection
Set selection1 = partDocument1.Selection

selection1.Clear

Dim part1 As Part
Set part1 = partDocument1.Part

Dim bodies1 As Bodies
Set bodies1 = part1.Bodies

Dim body1 As Body
Set body1 = bodies1.Item("PartBody")

Dim shapes1 As Shapes
Set shapes1 = body1.Shapes

Dim hole1 As Hole
Set hole1 = shapes1.Item("Hole.1")

selection1.Add hole1

selection1.Copy

Set partDocument1 = CATIA.ActiveDocument

Set selection1 = partDocument1.Selection

selection1.Clear

selection1.Add hole1

selection1.Paste

Dim hole2 As Hole
Set hole2 = shapes1.Item("Hole.6")

part1.Inactivate hole2

Dim sketch1 As Sketch
Set sketch1 = hole2.Sketch

part1.Inactivate sketch1

part1.Update

End Sub
